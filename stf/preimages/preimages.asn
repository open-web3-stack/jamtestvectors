-- Preimages STF test vectors schema

PreimagesModule DEFINITIONS ::= BEGIN

IMPORTS
    TimeSlot, OpaqueHash, PreimagesExtrinsic, ServiceId, ByteSequence, ServicesStatistics, U32
        FROM JamTypes;


PreimagesBlobMapEntry ::= SEQUENCE {
    hash OpaqueHash,
    blob ByteSequence
}

PreimagesRequestsMapKey ::= SEQUENCE {
    hash OpaqueHash,
    length U32
}

PreimagesRequestsMapEntry ::= SEQUENCE {
    key PreimagesRequestsMapKey,
    value SEQUENCE OF TimeSlot
}

-- Service account information relevant for this STF.
ServiceAccount ::= SEQUENCE {
    -- [a_p] Preimages blobs.
    preimage-blobs SEQUENCE OF PreimagesBlobMapEntry,
    -- [a_l] Preimages requests.
    preimage-requests SEQUENCE OF PreimagesRequestsMapEntry
}

ServiceAccountMapEntry ::= SEQUENCE {
    id ServiceId,
    data ServiceAccount
}

State ::= SEQUENCE {
	-- [δ] Relevant services account data. Refer to T(σ) in GP Appendix D.
    accounts SEQUENCE OF ServiceAccountMapEntry,
	-- [π_S] Services statistics.
	-- Note: Only stats related to preimages STF are updated, in particular:
	-- provided_count (p.0), provided_size (p.1).
    statistics ServicesStatistics
}

Input ::= SEQUENCE {
    -- [E_P] Preimages extrinsic.
    preimages PreimagesExtrinsic,
    -- [H_t] Block's timeslot.
    slot TimeSlot
}

-- State transition function execution error.
-- Error codes **are not specified** in the the Graypaper.
-- Feel free to ignore the actual value.
ErrorCode ::= ENUMERATED {
    preimage-unneeded (0),
    preimages-not-sorted-unique (1)
}

Output ::= CHOICE {
    ok  NULL,
    err ErrorCode
}

TestCase ::= SEQUENCE {
    input        Input,
    pre-state    State,
    output       Output,
    post-state   State
}

END
